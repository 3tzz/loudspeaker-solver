# -*- coding: utf-8 -*-
# version release 1.0
import PySide
from PySide import QtGui ,QtCore
from PySide.QtGui import *
from PySide.QtCore import *

import os

counter = 0
file_name = "FULL PATH DESTINATION" + "Altec816-{}.txt"

while os.path.isfile(file_name.format(counter)):
    counter += 1
file_name = file_name.format(counter)

file = open(file_name,'wt',newline='\r\n')      # open the file selected to write (w)

print("Exporting")

file.write("ID = 54.10"+"\n")
file.write("\n")
file.write("Comment = Altec817-1"+"\n")
file.write("\n")
file.write("|RADIATION, SOURCE AND MOUTH PARAMETER VALUES:"+"\n")
file.write("\n")
file.write("Ang = 2.0 x pi"+"\n")
file.write("Eg = 2.83"+"\n")
file.write("Rg = 0.00"+"\n")
file.write("Fta = 0.00"+"\n")
file.write("\n")
file.write("|HORN PARAMETER VALUES:"+"\n")
file.write("\n")
file.write("S1 = "+str("{:.2f}".format(float(App.ActiveDocument.Spreadsheet.A03/100)))+"\n")
file.write("S2 = "+str("{:.2f}".format(float(App.ActiveDocument.Spreadsheet.C03/100)))+"\n")
file.write("Par = "+str("{:.2f}".format(float(App.ActiveDocument.Spreadsheet.B03/10)))+"\n")
file.write("F12 = 0.00"+"\n")
file.write("S2 = "+str("{:.2f}".format(float(App.ActiveDocument.Spreadsheet.C03/100)))+"\n")
file.write("S3 = "+str("{:.2f}".format(float(App.ActiveDocument.Spreadsheet.E03/100)))+"\n")
file.write("Par = "+str("{:.2f}".format(float(App.ActiveDocument.Spreadsheet.D03/10)))+"\n")
file.write("F23 = 0.00"+"\n")
file.write("S3 = "+str("{:.2f}".format(float(App.ActiveDocument.Spreadsheet.E03/100)))+"\n")
file.write("S4 = "+str("{:.2f}".format(float(App.ActiveDocument.Spreadsheet.G03/100)))+"\n")
file.write("Par = "+str("{:.2f}".format(float(App.ActiveDocument.Spreadsheet.F03/10)))+"\n")
file.write("F34 = 0.00"+"\n")
file.write("S5 = "+str("{:.2f}".format(float(App.ActiveDocument.Spreadsheet.A05/100)))+"\n")
file.write("S6 = "+str("{:.2f}".format(float(App.ActiveDocument.Spreadsheet.C05/100)))+"\n")
file.write("Par = "+str("{:.2f}".format(float(App.ActiveDocument.Spreadsheet.B05/10)))+"\n")
file.write("F56 = 0.00"+"\n")
file.write("\n")
file.write("|TRADITIONAL DRIVER PARAMETER VALUES:"+"\n")
file.write("\n")
file.write("Sd = "+str("{:.2f}".format(float(App.ActiveDocument.Spreadsheet.A10/100)))+"\n")
file.write("Bl = "+str("{:.2f}".format(float(App.ActiveDocument.Spreadsheet.B10)))+"\n")
file.write("Cms = "+str("{:.2e}".format(float(App.ActiveDocument.Spreadsheet.C10)))+"\n")
file.write("Rms = "+str("{:.2f}".format(float(App.ActiveDocument.Spreadsheet.D10)))+"\n")
file.write("Mmd = "+str("{:.2f}".format(float(App.ActiveDocument.Spreadsheet.E10)))+"\n")
file.write("Le = "+str("{:.2f}".format(float(App.ActiveDocument.Spreadsheet.F10)))+"\n")
file.write("Re = "+str("{:.2f}".format(float(App.ActiveDocument.Spreadsheet.G10)))+"\n")
file.write("CH = 2P"+"\n")
file.write("\n")
file.write("|ADVANCED DRIVER PARAMETER VALUES FOR SEMI-INDUCTANCE MODEL:"+"\n")
file.write("\n")
file.write("Re' = "+str("{:.2f}".format(float(App.ActiveDocument.Spreadsheet.A12)))+"\n")
file.write("Leb' = "+str("{:.2f}".format(float(App.ActiveDocument.Spreadsheet.B12)))+"\n")
file.write("Le' = "+str("{:.2f}".format(float(App.ActiveDocument.Spreadsheet.C12)))+"\n")
file.write("Ke' = "+str("{:.2f}".format(float(App.ActiveDocument.Spreadsheet.D12)))+"\n")
file.write("Rss' = "+str("{:.2f}".format(float(App.ActiveDocument.Spreadsheet.E12)))+"\n")
file.write("\n")
file.write("|ADVANCED DRIVER PARAMETER VALUES FOR FREQUENCY-DEPENDENT DAMPING MODEL:"+"\n")
file.write("\n")
file.write("Rms = 0.00"+"\n")
file.write("Ams = 0.00"+"\n")
file.write("\n")
file.write("|PASSIVE RADIATOR PARAMETER VALUE:"+"\n")
file.write("\n")
file.write("Added Mass = 0.00"+"\n")
file.write("\n")
file.write("|CHAMBER PARAMETER VALUES:"+"\n")
file.write("\n")
file.write("Vrc = "+str("{:.2f}".format(float(App.ActiveDocument.Spreadsheet.D05/1000000)))+"\n")
file.write("Lrc = "+str("{:.2f}".format(float(App.ActiveDocument.Spreadsheet.E05/10)))+"\n")
file.write("Ap1 = "+str("{:.2f}".format(float(App.ActiveDocument.Spreadsheet.F05/100)))+"\n")
file.write("Lp = "+str("{:.2f}".format(float(App.ActiveDocument.Spreadsheet.G05/10)))+"\n")
file.write("Vtc = "+str("{:.2f}".format(float(App.ActiveDocument.Spreadsheet.H05/1000)))+"\n")
file.write("Atc = "+str("{:.2f}".format(float(App.ActiveDocument.Spreadsheet.I05/100)))+"\n")
file.write("\n")
file.write("Acoustic Path Length = 0.0"+"\n")
file.write("\n")
file.write("|MAXIMUM SPL PARAMETER VALUES:"+"\n")
file.write("\n")
file.write("Pamp = 100"+"\n")
file.write("Vamp = 25"+"\n")
file.write("Iamp = 4"+"\n")
file.write("Pmax = "+str("{:.2f}".format(float(App.ActiveDocument.Spreadsheet.H10)))+"\n")
file.write("Xmax = "+str("{:.2f}".format(float(App.ActiveDocument.Spreadsheet.I10)))+"\n")
file.write("\n")
file.write("Maximum SPL Setting = 3"+"\n")
file.write("\n")
file.write("|ABSORBENT FILLING MATERIAL PARAMETER VALUES:"+"\n")
file.write("\n")
file.write("Fr1 = 0.00"+"\n")
file.write("Fr2 = 0.00"+"\n")
file.write("Fr3 = 0.00"+"\n")
file.write("Fr4 = 0.00"+"\n")
file.write("\n")
file.write("Tal1 = 100"+"\n")
file.write("Tal2 = 100"+"\n")
file.write("Tal3 = 100"+"\n")
file.write("Tal4 = 100"+"\n")
file.write("\n")
file.write("|ACTIVE BAND PASS FILTER PARAMETER VALUES:"+"\n")
file.write("\n")
file.write("High Pass Frequency = 0"+"\n")
file.write("High Pass Slope = 1"+"\n")
file.write("Low Pass Frequency = 0"+"\n")
file.write("Low Pass Slope = 1"+"\n")
file.write("\n")
file.write("Butterworth High Pass Order = 1"+"\n")
file.write("Butterworth Low Pass Order = 1"+"\n")
file.write("Linkwitz-Riley High Pass Order = 2"+"\n")
file.write("Linkwitz-Riley Low Pass Order = 2"+"\n")
file.write("Bessel High Pass Order = 1"+"\n")
file.write("Bessel Low Pass Order = 1"+"\n")
file.write("\n")
file.write("2nd Order High Pass Q = 0.5"+"\n")
file.write("2nd Order Low Pass Q = 0.5"+"\n")
file.write("4th Order High Pass Q = 0.5"+"\n")
file.write("4th Order Low Pass Q = 0.5"+"\n")
file.write("\n")
file.write("Active Filter Alignment = 1"+"\n")
file.write("Active Filter On / Off Switch = 1"+"\n")
file.write("\n")
file.write("|PASSIVE FILTER PARAMETER VALUES:"+"\n")
file.write("\n")
file.write("Series / Parallel 1 = S"+"\n")
file.write("Series / Parallel 2 = S"+"\n")
file.write("Series / Parallel 3 = S"+"\n")
file.write("Series / Parallel 4 = S"+"\n")
file.write("\n")
file.write("|EQUALISER FILTER PARAMETER VALUES:"+"\n")
file.write("\n")
file.write("Band 1 Frequency = 0"+"\n")
file.write("Band 1 Q Factor = 0.01"+"\n")
file.write("Band 1 Gain = 0.0"+"\n")
file.write("Band 1 Type = -1"+"\n")
file.write("Band 2 Frequency = 0"+"\n")
file.write("Band 2 Q Factor = 0.01"+"\n")
file.write("Band 2 Gain = 0.0"+"\n")
file.write("Band 2 Type = -1"+"\n")
file.write("Band 3 Frequency = 0"+"\n")
file.write("Band 3 Q Factor = 0.01"+"\n")
file.write("Band 3 Gain = 0.0"+"\n")
file.write("Band 3 Type = -1"+"\n")
file.write("Band 4 Frequency = 0"+"\n")
file.write("Band 4 Q Factor = 0.01"+"\n")
file.write("Band 4 Gain = 0.0"+"\n")
file.write("Band 4 Type = -1"+"\n")
file.write("Band 5 Frequency = 0"+"\n")
file.write("Band 5 Q Factor = 0.01"+"\n")
file.write("Band 5 Gain = 0.0"+"\n")
file.write("Band 5 Type = -1"+"\n")
file.write("Band 6 Frequency = 0"+"\n")
file.write("Band 6 Q Factor = 0.01"+"\n")
file.write("Band 6 Gain = 0.0"+"\n")
file.write("Band 6 Type = -1"+"\n")
file.write("\n")
file.write("|STATUS FLAGS:"+"\n")
file.write("\n")
file.write("Auto Path Flag = 1"+"\n")
file.write("Lossy Inductance Model Flag = 0"+"\n")
file.write("Semi-Inductance Model Flag = 0"+"\n")
file.write("Damping Model Flag = 0"+"\n")
file.write("Closed Mouth Flag = 0"+"\n")
file.write("Continuous Flag = 1"+"\n")
file.write("\n")
file.write("|OTHER SETTINGS:"+"\n")
file.write("\n")
file.write("Filter Type Index = 0"+"\n")
file.write("Filter Input Index = 0"+"\n")
file.write("Filter Output Index = 0"+"\n")
file.write("\n")
file.write("Filter Type = 1"+"\n")
file.write("\n")
file.write("MEH Configuration = 0"+"\n")
file.write("ME Amplifer Polarity Value = 1"+"\n")

file.close()

print("File Saved  " + file_name)
